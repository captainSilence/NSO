module svi {

    namespace "http://example.com/svi";
    prefix svi;

    import ietf-inet-types {
        prefix inet;
    }
    import tailf-common {
        prefix tailf;
    }
    import tailf-ncs {
        prefix ncs;
    }

    description
      "Bla bla...";

    revision 2016-01-01 {
        description
          "Initial revision.";
    }
    augment /ncs:services {
        list svi {
            description
              "This is an RFS skeleton service";

            key name;
            leaf name {
                tailf:info "Unique service id";
                tailf:cli-allow-range;
                type string;
            }

            uses ncs:service-data;
            ncs:servicepoint svi-servicepoint;

            leaf vlan-id {
                tailf:info "Unique VLAN ID";
                mandatory true;
                type uint32 {
                    range "1..4096";
                }
            }

            list device {
                tailf:info "L3 switch";
                key name;
                leaf name {
                    tailf:info "Device name";
                    type leafref {
                        path "/ncs:devices/ncs:device/ncs:name";
                    }
                }

                leaf ip-prefix {
                    tailf:info "Unique IPv4 prefix for VLAN";
                    type inet:ip-prefix;
                }

                list interface {
                    tailf:info "Ethernet interface";
                    key "intf-type intf-id";

                    leaf intf-type {
                        tailf:info "Ethernet interface type";
                        type enumeration {
                            enum Ethernet;
                            enum FastEthernet;
                            enum GigabitEthernet;
                        }
                    }

                    leaf intf-id {
                        tailf:info "Ethernet interface ID";
                        type string;
                    }
                }
            }
        }
    }
}
